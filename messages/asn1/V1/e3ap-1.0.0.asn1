-- SPDX-FileCopyrightText: Copyright (c) 2026 Northeastern University
-- SPDX-License-Identifier: Apache-2.0

E3 DEFINITIONS AUTOMATIC TAGS ::= BEGIN

    E3-SetupRequest ::= SEQUENCE {
        e3apProtocolVersion  E3-Version,
        dAppName             E3-Name,
        dAppVersion          E3-Version,
        vendor               E3-Name,
        ...
    }

    E3-SetupResponse ::= SEQUENCE {
        requestId            E3-MessageID,
        responseCode         E3-ResponseCode,
        ranIdentifier        E3-Name,
        e3apProtocolVersion  E3-Version OPTIONAL,
        dAppIdentifier       E3-DAppID OPTIONAL,
        ranFunctionList      SEQUENCE (SIZE (0..64)) OF E3-RanFunctionDefinition OPTIONAL,
        ...,
        cause                E3-Cause OPTIONAL,
        detail               E3-Text OPTIONAL
    }

    E3-SubscriptionRequest ::= SEQUENCE {
        dAppIdentifier          E3-DAppID,
        ranFunctionIdentifier   INTEGER (1..65535),
        telemetryIdentifierList SEQUENCE (SIZE (0..256)) OF INTEGER (1..65535),
        controlIdentifierList   SEQUENCE (SIZE (0..256)) OF INTEGER (1..65535),
        subscriptionTime        INTEGER (0..86400) OPTIONAL,
        periodicity             INTEGER (0..60000000) OPTIONAL,
        ...
    }

    E3-SubscriptionDelete ::= SEQUENCE {
        dAppIdentifier        E3-DAppID,
        subscriptionId        INTEGER (1..65535),
        ...
    }

    E3-SubscriptionResponse ::= SEQUENCE {
        requestId            E3-MessageID,
        dAppIdentifier       E3-DAppID,
        responseCode         E3-ResponseCode,
        subscriptionId       INTEGER (1..65535) OPTIONAL,
        telemetryIdentifierList SEQUENCE (SIZE (0..256)) OF INTEGER (1..65535) OPTIONAL,
        controlIdentifierList   SEQUENCE (SIZE (0..256)) OF INTEGER (1..65535) OPTIONAL,
        ...,
        cause                   E3-Cause OPTIONAL,
        detail                  E3-Text OPTIONAL,
        ranFunctionIdentifier   INTEGER (1..65535) OPTIONAL,
        periodicity             INTEGER (0..60000000) OPTIONAL
    }

    E3-RanFunctionDefinition ::= SEQUENCE {
        ranFunctionIdentifier   INTEGER (1..65535),
        telemetryIdentifierList SEQUENCE (SIZE (0..256)) OF INTEGER (1..65535),
        controlIdentifierList   SEQUENCE (SIZE (0..256)) OF INTEGER (1..65535),
        ranFunctionData         OCTET STRING (SIZE (1..262144)),
        ...
    }

    E3-IndicationMessage ::= SEQUENCE {
        dAppIdentifier          E3-DAppID,
        ranFunctionIdentifier   INTEGER (1..65535),
        protocolData            OCTET STRING (SIZE (1..32768)),
        ...
    }

    E3-DAppControlAction ::= SEQUENCE {
        dAppIdentifier          E3-DAppID,
        ranFunctionIdentifier   INTEGER (1..65535),
        controlIdentifier       INTEGER (1..65535),
        -- Present only when the dApp is re-issuing a control it received as an
        -- E3-XAppControlAction, carrying that action's sequenceId back down so the
        -- RAN can match the applied control to the xApp procedure that asked for
        -- it. Absent on a control the dApp decided on its own.
        sequenceId              E3-SequenceID OPTIONAL,
        actionData              OCTET STRING (SIZE (1..32768)),
        ...,
        -- True when the dApp wants an E3-ControlResponse for this control. Absent
        -- reads as false. An extension addition, so a control that does not ask
        -- is encoded as it always was.
        requestAck              BOOLEAN OPTIONAL
    }

    E3-DAppReport ::= SEQUENCE {
        dAppIdentifier          E3-DAppID,
        ranFunctionIdentifier   INTEGER (1..65535),
        -- Assigned by the dApp. A report is the head of the E2-E3 loop, so this is
        -- the identifier every later message in that procedure carries: the RAN
        -- copies it into the E2SM-DAPP indication header as sequence-id, and an
        -- xApp reacting to this report echoes it on its control.
        sequenceId              E3-SequenceID,
        reportData              OCTET STRING (SIZE (1..32768)),
        ...
    }

    E3-XAppControlAction ::= SEQUENCE {
        dAppIdentifier          E3-DAppID,
        ranFunctionIdentifier   INTEGER (1..65535),
        -- Copied by the RAN's E2-E3 bridge from the E2SM-DAPP control header's
        -- sequence-id. Mandatory: a relayed xApp control that carried no id could
        -- never be matched to the control acknowledge the RAN owes the xApp.
        sequenceId              E3-SequenceID,
        xAppControlData         OCTET STRING (SIZE (1..32768)),
        ...,
        -- True when the RAN wants an E3-ControlResponse from the dApp for this
        -- control. Absent reads as false.
        requestAck              BOOLEAN OPTIONAL
    }

    E3-ReleaseMessage ::= SEQUENCE {
        dAppIdentifier       E3-DAppID,
        ...
    }

    -- DEPRECATED TO BE REMOVED. libe3 no longer sends it: the answer to a control
    -- is E3-ControlResponse. It stays in the grammar so that its index, and with it
    -- the index of controlResponse, is the one OCUDU's grammar has, and so that a
    -- libe3 dApp still reads the one that another RAN sends.
    E3-MessageAck ::= SEQUENCE {
        requestId            E3-MessageID,
        responseCode         E3-ResponseCode,
        ...,
        cause                E3-Cause OPTIONAL,
        detail               E3-Text OPTIONAL
    }

    -- The answer to a dApp control or an xApp control that carried requestAck
    -- true, sent by the receiver of the control: the RAN for a dApp control, the
    -- dApp for an xApp control. requestId is the id of the control's E3-PDU.
    -- The fields and their order are those of OCUDU's E3-ControlResponse minus
    -- fragmentIndex, fragmentCount and payloadBytes, which libe3 does not carry,
    -- so the encoding differs from OCUDU's. controlOutcome is service-model
    -- content and opaque here.
    E3-ControlResponse ::= SEQUENCE {
        requestId             E3-MessageID,
        dAppIdentifier        E3-DAppID,
        ranFunctionIdentifier INTEGER (1..65535),
        controlIdentifier     INTEGER (1..65535),
        responseCode          E3-ResponseCode,
        cause                 E3-Cause OPTIONAL,
        detail                E3-Text OPTIONAL,
        controlOutcome        OCTET STRING (SIZE (1..32768)) OPTIONAL,
        ...
    }

    -- Correlation identifier for one detection-to-mitigation procedure, assigned
    -- by whichever component originates it and propagated unchanged by everyone
    -- downstream. It is what crosses into E2SM-DAPP as sequence-id, so the E2 and
    -- E3 legs of a loop join per message instead of by nearest-in-time pairing.
    --
    -- Same range as E3-MessageID deliberately: both are producer-assigned counters
    -- with the same lifetime, and a shared range means neither can silently
    -- truncate when one is stored in a field sized for the other. Unlike a message
    -- id it is not reassigned per hop.
    E3-SequenceID ::= INTEGER (1..4294967295)

    E3-DAppID ::= INTEGER (1..65535)
    E3-MessageID ::= INTEGER (1..4294967295)
    E3-Name ::= OCTET STRING (SIZE (1..64))
    E3-Version ::= OCTET STRING (SIZE (1..32))
    -- Deliberately not extensible. An extensible ENUMERATED makes asn1c pass
    -- unknown values through as bare integers, which would turn every
    -- response-code switch in the encoders into a partial function. Adding a
    -- response code is a wire change we are willing to pay for explicitly.
    E3-ResponseCode ::= ENUMERATED { positive(0), negative(1) }

    -- Why a request was refused. Sent with a negative response next to a
    -- free-text detail. The names, the values and the text bound are OCUDU's,
    -- so a refusal reads the same on every RAN; the enumeration is extensible
    -- as it is there, and a receiver reads a value it does not know as
    -- unspecified. A negative response is still negative without either field.
    E3-Cause ::= ENUMERATED {
        unspecified(0), protocolError(1), setupRequired(2), setupAlreadyComplete(3),
        unsupportedProtocolVersion(4), unsupportedRanFunction(5), unsupportedIdentifier(6),
        invalidRequest(7), notFound(8), duplicate(9), resourceExhausted(10),
        authorizationRejected(11), payloadTooLarge(12), transportOverrun(13),
        shuttingDown(14), ...
    }

    -- UTF-8 text of up to 512 bytes, carried as an OCTET STRING as E3-Name is.
    E3-Text ::= OCTET STRING (SIZE (0..512))

    -- Nanoseconds since the Unix epoch on the realtime (UTC) clock. Never
    -- subtract it from a monotonic stamp.
    --
    -- Absent means "no producer reference", which is a normal message, not a
    -- malformed one: a producer that does not want the clock read on its data
    -- path simply omits it.
    --
    -- Unconstrained on purpose. asn1c renders this as a native signed integer
    -- and APER length-prefixes it, so the field widens by itself instead of
    -- capping the range, and the codec stays allocation-free on the
    -- indication path.
    --
    -- Do not "tighten" this to INTEGER (0..MAX): a semi-constrained INTEGER is
    -- APC_SEMI_CONSTRAINED, and asn1c 0.9.29's APER decoder has no branch for
    -- that flag and fails every decode. An explicit upper bound works but
    -- forces the arbitrary-precision INTEGER_t and a heap allocation per PDU.
    E3-Timestamp ::= INTEGER

    E3-PDU ::= SEQUENCE {
        id        E3-MessageID,
        timestamp E3-Timestamp OPTIONAL,
        msg       CHOICE {
            setupRequest          [0]  E3-SetupRequest,
            setupResponse         [1]  E3-SetupResponse,
            subscriptionRequest   [2]  E3-SubscriptionRequest,
            subscriptionDelete    [3]  E3-SubscriptionDelete,
            subscriptionResponse  [4]  E3-SubscriptionResponse,
            indicationMessage     [5]  E3-IndicationMessage,
            dAppControlAction     [6]  E3-DAppControlAction,
            dAppReport            [7]  E3-DAppReport,
            xAppControlAction     [8]  E3-XAppControlAction,
            releaseMessage        [9]  E3-ReleaseMessage,
            messageAck            [10] E3-MessageAck,   -- DEPRECATED TO BE REMOVED
            controlResponse       [11] E3-ControlResponse,
            ...
        },
        ...
    }

END
